-- SPDX-License-Identifier: BSD-3-Clause
--
-- Copyright (C) 2024 IETF Trust and the persons identified as authors
-- of the code
--
-- https://www.ietf.org/archive/id/draft-ietf-lamps-pq-composite-sigs-03.html

EdCompositeSignaturePrivateKey ::= SEQUENCE {
	firstPrivateKey BIT STRING ({ x509_mldsa_composite_private_key }),
	secondPrivateKey BIT STRING ({ x509_ed25519_private_key })
}
