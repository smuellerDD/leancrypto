-- SPDX-License-Identifier: BSD-3-Clause
--
-- Copyright (C) 2024 IETF Trust and the persons identified as authors
-- of the code
--

SignaturePrivateKey ::= SEQUENCE {
	privateKey BIT STRING ({ x509_slhdsa_private_key })
}
