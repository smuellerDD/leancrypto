-- SPDX-License-Identifier: BSD-3-Clause
--
-- Copyright (C) 2008 IETF Trust and the persons identified as authors
-- of the code
--
-- https://www.rfc-editor.org/rfc/rfc5280#section-4

BasicConstraints ::= SEQUENCE {
        cA                      BOOLEAN DEFAULT ({ x509_basic_constraints_ca }),
        pathLenConstraint       INTEGER OPTIONAL ({ x509_basic_constraints_pathlen })
}
